ESFormat-Ursula
{Z39-50-extendedService DBC(105) UrsulaItemOrder (1)} DEFINITIONS ::=
  -- oid is 1.2.840.10003.9.1000.105.3
BEGIN
IMPORTS InternationalString FROM Z39-50-APDU-1995;

-- Ursula Reserveringer / bestillinger
PDU ::= CHOICE {
    request          [1] Request,
    update           [2] Update,
    reservation      [3] Reservation,
    renewal          [4] Renewal
}

-- Foresporgsel
Request ::= SEQUENCE {
    libraryNo        [1] IMPLICIT LibraryNo OPTIONAL,
    borrowerTickerNo [2] IMPLICIT InternationalString OPTIONAL,
    disposalType     [3] IMPLICIT DisposalType OPTIONAL,
    lastUseDate      [4] IMPLICIT OCTET STRING OPTIONAL,
    items            [5] IMPLICIT SEQUENCE OF RequestItem,
    counter          [6] IMPLICIT ServiceCounter OPTIONAL,
    priority         [7] IMPLICIT Priority OPTIONAL,
    disposalNote     [8] IMPLICIT DisposalNote OPTIONAL,
    overrule         [9] IMPLICIT BOOLEAN OPTIONAL
}

-- Opdatering/sletning
Update ::= SEQUENCE {
    libraryNo        [1] IMPLICIT LibraryNo OPTIONAL,
    disposalId       [2] IMPLICIT OCTET STRING OPTIONAL,
    priority         [3] IMPLICIT Priority OPTIONAL,
    counter          [4] IMPLICIT ServiceCounter OPTIONAL,
    lastUseDate      [5] IMPLICIT OCTET STRING OPTIONAL,
    disposalNote     [6] IMPLICIT DisposalNote OPTIONAL
}

-- Eksemplarreserveringer
Reservation ::= CHOICE {
    request          [1] IMPLICIT RequestItem,
    update           [2] IMPLICIT SEQUENCE OF UpdateItem,
    del              [3] IMPLICIT DeleteItem
}

-- Fornyelse
Renewal ::= SEQUENCE {
    libraryNo        [1] IMPLICIT LibraryNo OPTIONAL,
    borrowerTicketNo [2] IMPLICIT BorrowerTicketNo OPTIONAL,
    copies           [3] IMPLICIT SEQUENCE OF InternationalString OPTIONAL,
    newReturnDate    [4] IMPLICIT InternationalString OPTIONAL,
    overrule         [5] IMPLICIT BOOLEAN OPTIONAL
}


RequestItem ::= SEQUENCE {
    id               [1] IMPLICIT OCTET STRING,
    titlePartNo      [2] IMPLICIT InternationalString
}

UpdateItem ::= SEQUENCE {
    copyNo           [1] IMPLICIT InternationalString,
    adviceTxt        [2] IMPLICIT InternationalString
}

DeleteItem ::= SEQUENCE {
    copyNo           [1] IMPLICIT InternationalString
}

DisposalType ::= OCTET STRING

BorrowerTicketNo ::= InternationalString

Priority ::= INTEGER

ServiceCounter ::= INTEGER

LibraryNo ::= InternationalString

DisposalNote ::= InternationalString
